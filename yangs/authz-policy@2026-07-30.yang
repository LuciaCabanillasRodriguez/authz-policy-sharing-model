module example-policy {
  namespace "urn:ietf:params:xml:ns:yang:example-policy";
  prefix policy;

  import ietf-inet-types {
    prefix inet;
  }

  import ietf-yang-provenance {
    prefix iyangprov;
  }

  organization
    "IETF NMOP Working Group";

  contact
    "WG Web:   <https://datatracker.ietf.org/wg/nmop/>

     WG List:  <mailto:nmop@ietf.org>

     Authors:
       Lucía Cabanillas
       <mailto:lucia.cabanillasrodriguez@telefonica.com>

       Diego López
       <mailto:diego.r.lopez@telefonica.com>

       Ana Méndez Pérez
       <mailto:ana.mendezperez@telefonica.com>;

       Pedro Martínez-Julia 
       <mailto:pedro@nict.go.jp>";

  description
    "Illustrative YANG model for representing distributed policies as managed artifacts";

  revision 2026-07-30 {
    description
      "Fifth revision";
    reference
      "RFC XXXX: Model for distributed
       policy sharing";
  }

  /*
   * Identities
   */

  identity policy-language {
    description
      "Abstract base identity for policy languages";
  }

  identity rego {
    base policy-language;
    description
      "Rego policy language";
  }

  identity cedar {
    base policy-language;
    description
      "Cedar policy language";
  }

  identity alfa {
    base policy-language;
    description
      "ALFA policy language";
  }

  identity xacml {
    base policy-language;
    description
      "XACML policy language";
  }

  /*
   * Typedefs
   */

  typedef policy-language-ref {
    type identityref {
      base policy-language;
    }
    description
      "Reference to a policy language identity";
  }

  /*
   * Policy model
   */

  container policy {
    description
      "Container representing a policy artifact";

    leaf area {
      type inet:uri;
      mandatory true;
      description
        "Administrative or operational area to which the policy belongs";
    }

    leaf description {
      type string;
      description
        "Optional human-readable description of the policy";
    }

    leaf language {
      type policy-language-ref;
      mandatory true;
      description
        "Specifies the policy language used to express the policy";
    }

    leaf policy-content {
      type string;
      mandatory true;
      description
        "Opaque policy content expressed in the language identified by the language leaf";
    }

    leaf owner {
      type inet:uri;
      mandatory true;
      description
        "URI identifying the authoritative entity responsible for this policy";
    }

    leaf author {
      type inet:uri;
      mandatory true;
      description
        "URI of the entity that authored the policy";
    }

    leaf origin {
      type inet:uri;
      description 
        "URI of the entity that originated this policy";
    }

    leaf policy-provenance {
      type iyangprov:provenance-signature;
      description
        "Cryptographic provenance signature associated with the policy";
    }
  }
}
